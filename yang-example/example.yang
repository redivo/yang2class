module example {
    yang-version 1.1;
    namespace "urn:example";
    prefix example;

    import base {
        prefix base;
    }

    description "Example module.";

    leaf my-int64 {
        type int64;
    }

    leaf my-uint64 {
        type uint64;
    }

    augment "/base:x/base:y/base:z" {
        description "Example augment.";
        leaf augmented {
            type int16;
        }
    }

    container my-container {
        description "Example container.";
        leaf my-leaf {
            type int8;
        }
    }

    list my-list {
        description "Example list.";
        key id;
        leaf id {
            type int32;
        }

        leaf content {
            type string;
        }

    }
}
