module example {
    yang-version 1.1;
    namespace "urn:example";
    prefix example;

    import base {
        prefix base;
    }

    description
        "This YANG module defines a component that describes the configuration of Interface Storm
         Control.";

    revision 2016-08-25 {
        description
            "Base model for Interface Storm Control.";
    }

    augment "/base:x-base/base:y_middle/base:z" {
        leaf augmented {
            type int16;
        }
    }

    container my-container-b {
        leaf olar {
            type int8;
        }
        leaf tudo_bem {
            type int32;
        }

        container my-container-a-a {
            leaf my-intra-leaf {
                type string;
            }
        }
    }

    leaf blz {
        type string;
    }

    list my-list {
        key id;
        leaf id {
            type int32;
        }

        leaf content {
            type int32;
        }

        list things {
            key name;
            leaf name {
                type string;
            }

            leaf x {
                type string;
            }
        }

        container inside-list-container {
            leaf content {
                type int32;
            }
        }
    }
}
